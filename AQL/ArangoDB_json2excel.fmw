FME workspace ArangoDB_json2excel.fmw

Parameters:
- ROOT_FOLDER = C:\Users\DriesVerdoodtNordend\OneDrive - Nordend\projects\AWV\0_projecten_awv\Lieven Duchateau\assets_Joris Vandenbosch   # Select the root folder (contains input JSON-file)
- ROOT_FOLDER_NAME:   # Scripted Parameter Value
      import fme
      from pathlib import Path
      
      def get_root_folder_name():
          """
          Retrieves the name of the root folder.
      
          Returns:
              str: The name of the root folder.
          """
          root_folder = fme.macroValues['ROOT_FOLDER']
          root_folder_path = Path(root_folder)
          return root_folder_path.name
      
      get_root_folder_name()
- SourceDataset_JSON = $(ROOT_FOLDER)/*.json   # Source JSON (JavaScript Object Notation) File or URL
- DestDataset_XLSXW = $(ROOT_FOLDER)/$(ROOT_FOLDER_NAME).xlsx   # Destination Microsoft Excel File

Readers:
- JSON_1: JSON from $(SourceDataset_JSON)

Writers:
- XLSXW_1: XLSXW to $(DestDataset_XLSXW)

Note: Dynamically set hyperlink to the first attribute (_key)
JSONFeature (reader JSON_1)
    attributes: uuid string, naam string, naampad string, toestand string, bestek_info.dossiernummer string, bestek_info.besteknummer string, bestek_info.aannemer string, bestek_info.van string, bestek_info.tot string, bestek_info.bestek_aannemer string, bestek_besteknummer string, bestekken_info string
    -> SchemaScanner
SchemaScanner
    CASE = No
    EMPTY_ATTR_HANDLING = SCANNER_DEFAULT
    HOLD = Yes
    IGNORE_REGEXP = ^fme_<pipe>^multi_<pipe>^json_
    INCLUDE_FORMAT_ATTR = No
    NUMERIC_ALLOW_LEADING_ZEROES = Yes
    SCHEMA_NAME_ATTR = fme_feature_type_name
    UNBOUNDED_NUMBERS = Yes
    UNBOUNDED_STRINGS = No
    -> FeatureMerger [REQUESTOR]
    <SCHEMA> -> PythonCaller
Note: set hyperlink to schema
PythonCaller
    PYTHONSOURCE:
      import fme
      from fme import BaseTransformer
      import fmeobjects


      class FeatureProcessor(BaseTransformer):
          """Template Class Interface:
          When using this class, make sure its name is set as the value of the 'Class to Process Features'
          transformer parameter.

          This class inherits from 'fme.BaseTransformer'. For full details of this class, its methods, and
          expected usage, see https://docs.safe.com/fme/html/fmepython/api/fme.html#fme.BaseTransformer.
          """

          def __init__(self):
              """Base constructor for class members."""
              self.log = fmeobjects.FMELogFile()

          def log2FME(self, message, severity=fmeobjects.FME_INFORM):
              """
              Sends message to the FME log file and console window.
              Severity must be one of FME_INFORM, FME_WARN, FME_ERROR,
              FME_FATAL, FME_STATISTIC, or FME_STATUSREPORT.
              """
              self.log.logMessageString(message, severity)

          def has_support_for(self, support_type: int):
              """This method is called by FME to determine if the PythonCaller supports Bulk mode,
              which allows for significant performance gains when processing large numbers of features.
              """
              return support_type == fmeobjects.FME_SUPPORT_FEATURE_TABLE_SHIM

          def input(self, feature: fmeobjects.FMEFeature):
              attr_names = feature.getAttribute('attribute{}.name')
              attr_types = feature.getAttribute('attribute{}.fme_data_type')

              # Create an attribute with suffix ".hyperlink" from the attribute at the first index position
              index = 0
              attr_names.insert(index + 1, f'{attr_names[index]}.hyperlink')
              attr_types.insert(index + 1, attr_types[index])

              feature.setAttribute('attribute{}.name', attr_names)
              feature.setAttribute('attribute{}.fme_data_type', attr_types)
              self.pyoutput(feature, output_tag="PYOUTPUT")

          def close(self):
              """This method is called once all the FME Features have been processed from input()."""
              pass

          def process_group(self):
              """This method is called by FME for each group when group processing mode is enabled."""
              pass

          def reject_feature(self, feature: fmeobjects.FMEFeature, code: str, message: str):
              """This method can be used to output a feature to the <Rejected> port."""
              feature.setAttribute("fme_rejection_code", code)
              feature.setAttribute("fme_rejection_message", message)
              self.pyoutput(feature, output_tag="<Rejected>")
    PYTHONSYMBOL = FeatureProcessor
    -> FeatureMerger [SUPPLIER]
FeatureMerger
    ATTR_ACCUM_MODE = Merge Supplier
    ATTR_CONFLICT_RES_LOOKUP = REQUESTOR_IF_CONFLICT
    IGNORE_NULLS = No
    JOIN_KEYS = 1 1 AUTO
    MERGE_TYPE_VAL = ATTRIBUTES
    PROCESS_DUPS = NO
    REJECT_NULL_MISSING_KEYS = No
    SUPPLIERS_FIRST = No
    ATTR_CONFLICT_RES = Use Requestor
    MERGE_TYPE = Attributes Only
    MERGED -> PythonCaller_2
PythonCaller_2
    PYTHONSOURCE:
      import fme
      from fme import BaseTransformer
      import fmeobjects


      class FeatureProcessor(BaseTransformer):
          """Template Class Interface:
          When using this class, make sure its name is set as the value of the 'Class to Process Features'
          transformer parameter.

          This class inherits from 'fme.BaseTransformer'. For full details of this class, its methods, and
          expected usage, see https://docs.safe.com/fme/html/fmepython/api/fme.html#fme.BaseTransformer.
          """

          def __init__(self):
              """Base constructor for class members."""
              pass

          def has_support_for(self, support_type: int):
              """This method is called by FME to determine if the PythonCaller supports Bulk mode,
              which allows for significant performance gains when processing large numbers of features.
              """
              return support_type == fmeobjects.FME_SUPPORT_FEATURE_TABLE_SHIM

          def input(self, feature: fmeobjects.FMEFeature):
              attr_name = feature.getAttribute('attribute{0}.name')
              attr_value = feature.getAttribute(attr_name)

              attr_name_hyperlink = f'{attr_name}.hyperlink'
              attr_value_hyperlink = f'https://apps.mow.vlaanderen.be/eminfra/assets/{attr_value}'

              feature.setAttribute(attr_name_hyperlink, attr_value_hyperlink)

              self.pyoutput(feature, output_tag="PYOUTPUT")

          def close(self):
              """This method is called once all the FME Features have been processed from input()."""
              pass

          def process_group(self):
              """This method is called by FME for each group when group processing mode is enabled."""
              pass

          def reject_feature(self, feature: fmeobjects.FMEFeature, code: str, message: str):
              """This method can be used to output a feature to the <Rejected> port."""
              feature.setAttribute("fme_rejection_code", code)
              feature.setAttribute("fme_rejection_message", message)
              self.pyoutput(feature, output_tag="<Rejected>")
    PYTHONSYMBOL = FeatureProcessor
    -> Sheet1 (writer XLSXW_1)
Sheet1 (writer XLSXW_1)
Note: Custom Transformer relict
setHyperlink [off]
    ATTRIBUTE = @Value(attribute{0}.name)

FME custom transformer setHyperlink

Parameters:
- ATTRIBUTE = @Value(uuid)   # uuid

Input (input)
    -> AttributeCreator_2
Note: Hyperlinks maken voor de asset-uuid
AttributeCreator_2
    ATTR_TABLE = SET_TO uuid.hyperlink (varchar(200)) = https://apps.mow.vlaanderen.be/eminfra/assets/$(ATTRIBUTE)
    -> Output (output)
Output (output)
