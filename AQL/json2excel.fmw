FME workspace json2excel.fmw

Parameters:
- SourceDataset_JSON = C:\Users\DriesVerdoodtNordend\Downloads\download.json   # Source JSON (JavaScript Object Notation) File or URL
- DestDataset_XLSXW = export_Miguel_20260129   # Destination Microsoft Excel File

Readers:
- JSON_1: JSON from $(SourceDataset_JSON)

Writers:
- XLSXW_1: XLSXW to $(DestDataset_XLSXW)

JSONFeature (reader JSON_1)
    attributes: uuid string, naam string, naampad string, toestand string, bestekken string, bestek_aannemer string
    -> setHyperlink
setHyperlink
    BESTEKKEN = @Value(bestekken)
    NAAM = @Value(naam)
    NAAMPAD = @Value(naampad)
    TOESTAND = @Value(toestand)
    UUID = @Value(uuid)
    -> assets_en_bestekken (writer XLSXW_1)
assets_en_bestekken (writer XLSXW_1)
    attributes: uuid.hyperlink string(200), uuid string(20), naam string(20), naampad string(20), toestand string(20), bestekken string(20), bestek_aannemer string(20)
Note: De lijst met bestekken (asset en parent-asset) omvormen naar een string.
PythonCaller
    NEW_ATTRIBUTES = bestekken buffer parent_bestekken buffer
    PYTHONSOURCE:
      import fme
      from fme import BaseTransformer
      import fmeobjects


      class FeatureProcessor(BaseTransformer):
          """Template Class Interface:
          When using this class, make sure its name is set as the value of the 'Class to Process Features'
          transformer parameter.

          This class inherits from 'fme.BaseTransformer'. For full details of this class, its methods, and
          expected usage, see https://docs.safe.com/fme/html/fmepython/api/fme.html#fme.BaseTransformer.
          """

          def __init__(self):
              """Base constructor for class members."""
              pass

          def has_support_for(self, support_type: int):
              """This method is called by FME to determine if the PythonCaller supports Bulk mode,
              which allows for significant performance gains when processing large numbers of features.
              """
              return support_type == fmeobjects.FME_SUPPORT_FEATURE_TABLE_SHIM

          def format_bestek_info(self, aannemer: list, besteknummer: list, dossiernummer: list, van: list, tot: list) -> str:
              """
              Format list info van bestekken naar 1 string.
              """
              nbr_bestekken = len(besteknummer)
              bestekken = []
              for i in range(len(besteknummer)):
                  bestek = f'aannemer: {aannemer[i]}, besteknumer: {besteknummer[i]}, dossiernummer: {dossiernummer[i]}, van: {van[i]}, tot: {tot[i]}'
                  bestekken.append(bestek)
              bestekken_str = '; '.join(bestekken)
              return bestekken_str

          def input(self, feature: fmeobjects.FMEFeature):
              """This method is called for each feature which enters the PythonCaller."""
              # bestekken van de asset (a)
              a_aannemer = feature.getAttribute('bestekken{}.aannemer')
              a_besteknummer = feature.getAttribute('bestekken{}.besteknummer')
              a_dossiernummer = feature.getAttribute('bestekken{}.dossiernummer')
              a_van = feature.getAttribute('bestekken{}.van')
              a_tot = feature.getAttribute('bestekken{}.tot')

              if a_besteknummer:
                  bestekken_str = self.format_bestek_info(aannemer=a_aannemer, besteknummer=a_besteknummer, dossiernummer=a_dossiernummer, van=a_van, tot=a_tot)
                  feature.setAttribute('bestekken', bestekken_str)

              # bestekken van de parent-asset (p)
              p_aannemer = feature.getAttribute('parent_bestekken{}.aannemer')
              p_besteknummer = feature.getAttribute('parent_bestekken{}.besteknummer')
              p_dossiernummer = feature.getAttribute('parent_bestekken{}.dossiernummer')
              p_van = feature.getAttribute('parent_bestekken{}.van')
              p_tot = feature.getAttribute('parent_bestekken{}.tot')

              if p_besteknummer:
                  bestekken_str = self.format_bestek_info(aannemer=p_aannemer, besteknummer=p_besteknummer, dossiernummer=p_dossiernummer, van=p_van, tot=p_tot)
                  feature.setAttribute('parent_bestekken', bestekken_str)

              self.pyoutput(feature, output_tag="PYOUTPUT")

          def close(self):
              """This method is called once all the FME Features have been processed from input()."""
              pass

          def process_group(self):
              """This method is called by FME for each group when group processing mode is enabled."""
              pass

          def reject_feature(self, feature: fmeobjects.FMEFeature, code: str, message: str):
              """This method can be used to output a feature to the <Rejected> port."""
              feature.setAttribute("fme_rejection_code", code)
              feature.setAttribute("fme_rejection_message", message)
              self.pyoutput(feature, output_tag="<Rejected>")
    PYTHONSYMBOL = FeatureProcessor
    -> AttributeCreator
Note: Hyperlinks maken voor de asset-uuid
AttributeCreator
    ATTR_TABLE:
      SET_TO uuid.hyperlink (varchar(200)) = https://apps.mow.vlaanderen.be/eminfra/assets/@Value(uuid)
      SET_TO parent_key.hyperlink (varchar(200)) = https://apps.mow.vlaanderen.be/eminfra/assets/@Value(parent_key)

FME custom transformer setHyperlink

Parameters:
- UUID = @Value(uuid)   # uuid
- BESTEKKEN = @Value(bestekken)   # bestekken
- NAAM = @Value(naam)   # naam
- NAAMPAD = @Value(naampad)   # naampad
- TOESTAND = @Value(toestand)   # toestand

Input (input)
    -> AttributeCreator_2
Note: Hyperlinks maken voor de asset-uuid
AttributeCreator_2
    ATTR_TABLE = SET_TO uuid.hyperlink (varchar(200)) = https://apps.mow.vlaanderen.be/eminfra/assets/@Value(uuid)
    -> Output (output)
Output (output)
